ASN-Module-FixedPointData { iso(1) identified-organization(3) dod(6)
    internet(1) private(4) enterprise(1) uic(17218) fcb(1) modules(0) fpd(6) v1(1) 0 }
    DEFINITIONS AUTOMATIC TAGS ::= BEGIN

IMPORTS GenericId, CompanyCode, Station, CoachPlaces, Data, SharedVehicleVariety, SharedVehiclePropulsionType,
 SharedVehicleReturnConstraint, TransportId, LineId, UnicodeText
 FROM ASN-Module-GeneralData { iso(1) identified-organization(3) dod(6) internet(1) private(4) enterprise(1) uic(17218) fcb(1) modules(0) general(5) v1(1) 0 };

-- ##############################################################################################
-- # UIC Fixed Point Data - version 1.0.0
-- # Value "FPD1" in element dataFormat of the UICBarcodeHeader.
-- #
-- # The UICBarcodeHeader need not be signed (i.e. level1Signature unset), if the situation does not require it.
-- #
-- # Optional format for combining a FixedPointData structure with a URL for inclusion in a QR code.
-- # This is useful, for example, in the case of customer feedback barcodes that should link to the operator's website
-- # for reporting faults, or for directing users to download an app to access a shared vehicle.
-- #   (1) Encode this structure in the DOSIPAS format in the usual way, optionally signed
-- #   (2) Base-41 encode the resultant binary data, with the alphabet "0123456789ABCDEFGHIJKLMNOPQRSTUVWXYZ$*-.:"; see here: https://github.com/sveljko/base41
-- #   (3) Append it to the end of a URL with the prefix "$UIC:"
-- # Example: "HTTPS://RAIL.EXAMPLE/QRFB/$UIC:A2I9..."
-- # n.b. uppercase should be used in the whole URL, as this is much more efficient to encode in a QR code
-- #
-- # Encoding in an NFC tag
-- #   (1) Encode this structure in the DOSIPAS format in the usual way, optionally signed
-- #   (2) Place the encoded DOSIPAS in an NDEF record of the format 0x02 (IANA Media Type),
-- #         with the media type application/vnd.uic.dosipas.v2 or application/vnd.uic.dosipas.v1, as appropriate
-- #   (3) Write the NDEF record to an NDEF formatted NFC tag
-- # Other records may exist in the same NDEF message. Readers MUST be prepared to look beyond the
-- #  first record to find a UIC DOSIPAS record.
-- ##############################################################################################

FixedPointData ::= SEQUENCE {
    -- The ID should be eternally unique per issuer
    id          GenericId,
    -- If different from the security provider
    -- Required to be set if the barcode is unsigned (i.e. no security provider)
    issuer      CompanyCode         OPTIONAL,
    specimen    BOOLEAN,
    affixedTo   Object              OPTIONAL,
    -- Additional important information about this fixed point
    infoText    UnicodeText         OPTIONAL,
    extension   SEQUENCE OF Data    OPTIONAL,
    ...
}

Object ::= CHOICE {
    station         Station,        -- for check-in/check-out by scanning
    vehicle         Vehicle,        -- e.g. for at-seat ordering, customer reporting of vehicle defects, vehicle based check-in
    sharedVehicle   SharedVehicle,  -- e.g. bike, e-scooter, car sharing
    proprietary     GenericId,      -- defined by the issuer
    vehicleDynamic  VehicleDynamic,
    ...
}

Station ::= SEQUENCE {
    station                 Station,
    platform                VisibleString   OPTIONAL,
    subLocationProprietary  GenericId       OPTIONAL, -- defined by the issuer
    ...
}

Vehicle ::= SEQUENCE {
    id                      VehicleIdentifier,
    place                   CoachPlaces             OPTIONAL, -- for identifying at which carriage and seat/compartment this barcode is placed, if at a seat
    subLocationProprietary  GenericId               OPTIONAL, -- when affixed non-seat items or sub-items within a compartment, defined by the issuer
    ...
}

-- Representing a barcode/tag that is updated as the vehicle progresses along its route
VehicleDynamic ::= SEQUENCE {
    vehicleId               VehicleIdentifier,
    currentStop             Station,
    transport               TransportId         OPTIONAL,
    line                    LineId              OPTIONAL,
    terminusStop            Station,
    ...
}

VehicleIdentifier ::= CHOICE {
    evn             INTEGER (0..999999999999),                              -- ERA European Vehicle Number, including the check digit
    vin             VisibleString (SIZE(17) ^ FROM ("A".."Z"|"0".."9")),    -- VIN per ISO 3779
    proprietary     GenericId,                                              -- defined by the issuer
    ...
}

-- Built upon GBFSv3.0
-- Reference: https://github.com/MobilityData/gbfs-json-schema/blob/master/v3.0/vehicle_types.json
SharedVehicle ::= SEQUENCE {
    id                  GenericId, -- defined by the issuer
    variety             SharedVehicleVariety,
    propulsion          SharedVehiclePropulsionType,
    returnConstraint    SharedVehicleReturnConstraint,
    ...
}

END
